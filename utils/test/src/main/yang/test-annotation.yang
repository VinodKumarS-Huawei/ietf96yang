module test-annotation {  
    namespace "test:test-annotation";  
    prefix ta ;
  
    import test{ 
       prefix test;
    }
    
    revision "2015-12-16" {  
       reference "";  
    }  
     
    ca:compiler-annotation /test:list1/test:list2{ 
        ds:app-data-structure "queue" ;
    }

    ca:compiler-annotation /test:list1{ 
        ds:app-data-structure "queue" ;
        ae:app-extended "special-list";
    }
}
