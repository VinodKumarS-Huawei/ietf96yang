module test {  
    namespace "test:test";  
    prefix test ;  
       
    revision "2015-12-16" {  
       reference "";  
    }  

    list list1 {
        key "leaf1";
        leaf leaf1 {
            type int32;
        }
        list list2 {
           key "leaf2";
           leaf leaf2 {
              type int32;
           }
        }
     }

    container cont1 {
        container cont2 {
           leaf leaf {
              type int32;
           }
        }
     }
}
