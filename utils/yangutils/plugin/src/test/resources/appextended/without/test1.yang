module test {

  namespace "urn:ietf:params:xml:ns:yang:ietf-ipv4-unicast-routing";

  prefix "test";

   list list1 {
       key "leaf1";
       leaf leaf1 {
           type int32;
        }
       list list2 {
           key "leaf2";
           leaf leaf2 {
                type int32;
            }
       }
    } 
 
    container cont1 {
          leaf leaf {
              type int32;
           }
    }

}
